FME workspace ifc_to_gltf_annotation_json.fmw

Parameters:
- DestDataset_JSON = .\json\annotations.json   # Destination JSON (JavaScript Object Notation) File
- DestDataset_GLTF = .\gltf   # Destination glTF Folder

Writers:
- JSON_1: JSON to $(DestDataset_JSON)
- GLTF_1: GLTF to $(DestDataset_GLTF)

Creator
    GEOMTYPE = Geometry Object
    NUM = 1
    CREATED -> HTTPCaller
Note: source: Institute for Automation and Applied Informatics (IAI) / Karlsruhe Institute of Technology (KIT) or Institut für Automation und angewandte Information / Karlsruher Institut für Technologie / https://www.ifcwiki.org/index.php?title=KIT_IFC_Examples
HTTPCaller
    CONNECTION_TIMEOUT_LENGTH = 60
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_FILENAME = .\ifc\AC20-FZK-Haus.ifc
    REDIRECT_AUTH = ORIGINAL_DOMAIN_ONLY
    RESPONSE_TYPE = File
    STATUS_CODE_ATTR = _http_status_code
    TARGET_URL = http://www.ifcwiki.org/images/e/e3/AC20-FZK-Haus.ifc
    TRANSFER_TIMEOUT_LENGTH = 90
    USE_COOKIES = No
    VERIFY_SSL_CERTIFICATES = Yes
    -> FeatureReader [INITIATOR]
FeatureReader
    ATTRS_TO_EXPOSE = ifc_unique_id ifc_parent_id GlobalId Description fme_feature_type
    ATTR_ACCUM_MODE = Merge Initiator and Result
    ATTR_CONFLICT_RES = Use Result
    ATTR_IGNORE_NULLS = No
    COMBINE_GEOM = Use Result
    DATASET = @Value(_response_file_path)
    FORMAT = IFC
    IFC_ADD_PROJECTIONS = Yes
    IFC_CREATE_PQSET_DEFINITION_FEATURES = No
    IFC_EVALUATE_CSG_SOLIDS = Yes
    IFC_IFCSPACE_GEOMETRY = Yes
    IFC_MERGE_TYPE_OBJECT_PQSETS = YES
    IFC_PQSET_READ_MODE = FEATURES
    IFC_PREDEFINED_REPRESENTATION_IDENTIFIERS = Annotation Axis Body
    IFC_READER_MODE = Relational
    IFC_READER_VERSION = 2014
    IFC_READ_ALL_REPRESENTATIONS = NO
    IFC_SIMPLIFY_BASE_FACES = Yes
    IFC_STRING_ENCODING = utf-8
    IFC_SUBTRACT_OPENINGS = Yes
    IFC_TYPE_OBJECT_READ_MODE = MERGED
    IFC_USE_SEARCH_ENVELOPE = NO
    IFC_VERSION_OVERRIDE = auto-detect
    INTERACT = NONE
    OUTPUT_FEATURES_DISPLAY = Schema and Data Features
    <OTHER> -> fme_feature_type_is_IfcAnnotation
Note: Tester: / fme_feature_typeがIfcAnnotationのfeatureのみを抽出する。
fme_feature_type_is_IfcAnnotation: Tester
    BOOL_OP = OR
    TEST_CLAUSE = TEST @Value(fme_feature_type) = IfcAnnotation
    TEST_MODE = TEST
    PASSED -> Deaggregator
Note: FMETextとそれ以外をより分けるためにバラバラにする。
Deaggregator
    ATTR_ACCUM_MODE = Merge List Attributes
    ATTR_CONFLICT_RES = Use List Attribute Values
    EXPLODE_INSTANCES = Yes
    GEOM_NAME_FIELD = _geometry_name
    LIST_ATTR_MODE_LOOKUP = LEAN
    MODE = Flatten One Level
    PART_NUMBER_FIELD = _part_number
    SPLIT_COMPOSITES = Yes
    DEAGGREGATED -> PythonCaller
Note: FMEText型のgeometryだった場合、以下の属性を付与する / 属性名 / 説明 / _is_text / True / _text / FMEText#getTextString()の結果 / _minx / FMEText#boundingCube()の結果(minx) / _miny / FMEText#boundingCube()の結果(miny) / _minz / FMEText#boundingCube()の結果(minz) / _maxx / FMEText#boundingCube()の結果(maxx) / _maxy / FMEText#boundingCube()の結果(maxy) / _maxz / FMEText#boundingCube()の結果(maxz) / _text_rotate_ccw_degree / FMEText#getTextRotation()の結果
PythonCaller
    NEW_ATTRIBUTES = _is_text _text _rotation_ccw_degree _minx _miny _minz _maxx _maxy _maxz _px _py _pz
    PYTHONSOURCE:
      import fme
      import fmeobjects
      import traceback
      from fmeobjects import FMEText

      logger = fmeobjects.FMELogFile()

      def processFeature(feature):
          try:
              geom = feature.getGeometry()
              if (type(geom) is FMEText):
                  feature.setAttribute('_is_text', True)
                  feature.setAttribute('_text', geom.getTextString())
                  feature.setAttribute('_rotation_ccw_degree', geom.getTextRotation())
                  (min, max) = geom.boundingCube()
                  feature.setAttribute('_minx', min[0])
                  feature.setAttribute('_miny', min[1])
                  feature.setAttribute('_minz', min[2])
                  feature.setAttribute('_maxx', max[0])
                  feature.setAttribute('_maxy', max[1])
                  feature.setAttribute('_maxz', max[2])
                  p = geom.getLocation(True)
                  (x, y, z) = p.getXYZ()
                  feature.setAttribute('_px', x)
                  feature.setAttribute('_py', y)
                  feature.setAttribute('_pz', z)
          except:
              tb = traceback.format_exc()
              logger.logMessageString(tb, fmeobjects.FME_ERROR)
    PYTHONSYMBOL = processFeature
    -> _is_text
Note: Tester: / FMETextとそれ以外を選り分け
_is_text: Tester
    BOOL_OP = OR
    TEST_CLAUSE = TEST @Value(_is_text) = Yes
    TEST_MODE = TEST
    PASSED -> Inspector
    PASSED -> annotation_text_json (writer JSON_1)
    FAILED -> annotation_lines (writer GLTF_1)
Note: 途中経過確認用その２
Inspector
Note: JsonWriter: / FMETextはjsonとして出力する。 / jsonの属性としてPythonCallerで付与した属性(_text, _text_rotate_ccw, _minx, _miny, _minz, _maxx, _maxy, _maxz)を書き出す。
Note: ここから先はjsonをもとに以下の手順でglTFを作成。 / 1. (_minx, _maxx, _minz, _maxx, _maxy, _maxz)の範囲を持つ板ポリゴンを作る / 2. _textをもとにテクスチャ画像を生成 / 3. 1に2を張り付ける / 4. glTFで出力 / 頑張ればPythonCallerでもできる？かもだけど / 今回は別プログラムとした。
annotation_text_json (writer JSON_1)
    attributes: GlobalId string, _text string, _rotation_ccw_degree float, _minx float, _miny float, _minz float, _maxx float, _maxy float, _maxz float, Name string, Description string, ObjectType string, Annotation string, Axis string, Body string, Box string, FootPrint string, ApplicableOccurrence string, BuildingAddress.AddressLines string, BuildingAddress.Country string, BuildingAddress.Description string, BuildingAddress.InternalLocation string, BuildingAddress.PostalBox string, BuildingAddress.PostalCode string, BuildingAddress.Purpose string, BuildingAddress.Region string, BuildingAddress.Town string, BuildingAddress.UserDefinedPurpose string, CompositionType string, ElementType string,
      Elevation float, ElevationOfRefHeight float, ElevationOfTerrain float, ElevationWithFlooring float, LandTitleNumber string, LongName string, OperationType string, OverallHeight float, OverallWidth float, PartitioningType string, Phase string, PredefinedType string, RefElevation float, RefLatitude float, RefLongitude float, SiteAddress.AddressLines string, SiteAddress.Country string, SiteAddress.Description string, SiteAddress.InternalLocation string, SiteAddress.PostalBox string, SiteAddress.PostalCode string, SiteAddress.Purpose string, SiteAddress.Region string, SiteAddress.Town string, SiteAddress.UserDefinedPurpose string, Tag string, UserDefinedOperationType string, UserDefinedPartitioningType string, ifc_parent_id string, ifc_parent_unique_id string,
      ifc_type_name string, ifc_type_object_id string, ifc_unique_id string
Note: GltfWriter: / FMEText以外のgeometryはそのままglTFとして書き出す / → 引き出し線形状のみのglTFになる
annotation_lines (writer GLTF_1)
